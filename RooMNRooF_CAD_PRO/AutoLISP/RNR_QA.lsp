;;; RNR_QA.lsp - lightweight QA (LISP). Full QA: RNRQA (.NET).
;;; Reports only what is actually checked; nothing is reported PASS without a check.
(defun rnr:count-ss (flt / ss) (if (setq ss (ssget "_X" flt)) (sslength ss) 0))

(defun c:RNRL-QA ( / missing n0 ovr txt errs warns)
  (setq errs 0 warns 0 missing nil)
  (foreach l '("S-GRID" "S-COL" "S-BEAM" "A-WALL" "ANNO-TEXT" "ANNO-TITLE")
    (if (not (tblsearch "LAYER" l)) (setq missing (cons l missing))))
  (setq n0 (rnr:count-ss '((8 . "0") (-4 . "<NOT") (0 . "INSERT") (-4 . "NOT>"))))
  (setq ovr (rnr:count-ss '((-4 . "<OR") (62 . 1) (62 . 2) (62 . 3) (62 . 4) (62 . 5) (62 . 6) (62 . 7) (-4 . "OR>"))))
  (setq txt (rnr:count-ss '((0 . "TEXT,MTEXT") (-4 . "<NOT") (7 . "RNR_*") (-4 . "NOT>"))))
  (princ "\n=====================================")
  (princ "\nRooMNRooF CAD QA (LISP quick check)")
  (princ "\n=====================================")
  (princ (strcat "\nAutoCAD: " (getvar "ACADVER") "   Drawing: " (getvar "DWGNAME")))
  (princ (strcat "\nLayers              " (if missing (progn (setq warns (1+ warns)) "WARNING") "PASS")))
  (if missing (foreach m missing (princ (strcat "\n   missing " m))))
  (princ (strcat "\nObjects on layer 0  " (if (> n0 0) (progn (setq warns (1+ warns)) (strcat "WARNING (" (itoa n0) ")")) "PASS")))
  (princ (strcat "\nColour overrides    " (if (> ovr 0) (progn (setq warns (1+ warns)) (strcat "WARNING (" (itoa ovr) " ACI 1-7)")) "PASS")))
  (princ (strcat "\nText styles         " (if (> txt 0) (progn (setq warns (1+ warns)) (strcat "WARNING (" (itoa txt) " non-RNR)")) "PASS")))
  (princ (strcat "\nUnits               " (if (/= (getvar "INSUNITS") 4) (progn (setq warns (1+ warns)) "WARNING (INSUNITS not mm)") "PASS")))
  (princ "\nLayouts/Plot/Title  NOT_CHECKED (use RNRQA)")
  (princ (strcat "\nErrors: " (itoa errs) "   Warnings: " (itoa warns)))
  (princ "\n=====================================")
  (princ))
(princ)
