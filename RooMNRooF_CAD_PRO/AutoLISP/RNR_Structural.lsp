;;; RNR_Structural.lsp - columns, beams, footings with member marks (LISP versions)
;;; The .NET commands (RNRCOLUMN etc.) additionally attach schedule metadata; these LISP
;;; versions draw geometry + marks and are useful in AutoCAD LT-like/limited environments.
(defun c:RNRL-COLUMN ( / ty w d id p cnt)
  (rnr:start '("CMDECHO" "OSMODE" "HPASSOC"))
  (setvar "CMDECHO" 0)
  (rnr:layers-apply "S-COL,S-COL-TEXT,S-HATCH")
  (setq ty (rnr:getkw "Column type" "Rectangular Square Circular" "Rectangular"))
  (cond
    ((= ty "Circular") (setq w (rnr:getposreal "Diameter (mm)" 400.0) d w))
    ((= ty "Square") (setq w (rnr:getposreal "Side (mm)" 350.0) d w))
    (T (setq w (rnr:getposreal "Width (mm)" 300.0) d (rnr:getposreal "Depth (mm)" 450.0))))
  (setq id (rnr:getstr "Column ID" "C1") cnt 0)
  (while (setq p (getpoint "\nColumn centre <done>: "))
    (setvar "CLAYER" "S-COL")
    (if (= ty "Circular") (rnr:circle p (/ w 2.0) "S-COL") (rnr:rect p w d "S-COL"))
    (rnr:text (list (+ (car p) (/ w 2.0) 150) (+ (cadr p) (/ d 2.0) 150)) id (* 2.5 (rnr:scale)) "S-COL-TEXT")
    (setq cnt (1+ cnt)))
  (princ (strcat "\n[RNR] " (itoa cnt) " column(s) " id " placed."))
  (rnr:end) (princ))

(defun c:RNRL-BEAM ( / w dp id a b ang n off)
  (rnr:start '("CMDECHO"))
  (rnr:layers-apply "S-BEAM,S-BEAM-TEXT")
  (setq w (rnr:getposreal "Beam width (mm)" 250.0) dp (rnr:getposreal "Beam depth (mm)" 450.0)
        id (rnr:getstr "Beam ID" "B1"))
  (while (setq a (getpoint "\nBeam start <done>: "))
    (if (setq b (getpoint a "\nBeam end: "))
      (progn
        (setq ang (angle a b) n (+ ang (/ pi 2)) off (/ w 2.0))
        (rnr:line (polar a n off) (polar b n off) "S-BEAM")
        (rnr:line (polar a (+ n pi) off) (polar b (+ n pi) off) "S-BEAM")
        (rnr:text (polar (polar a ang (/ (distance a b) 2.0)) n (+ off (* 3.0 (rnr:scale))))
                  (strcat id " (" (rtos w 2 0) "x" (rtos dp 2 0) ")") (* 2.5 (rnr:scale)) "S-BEAM-TEXT"))))
  (rnr:end) (rnr:ok))

(defun c:RNRL-FOOTING ( / l w thk id p c)
  (rnr:start '("CMDECHO"))
  (rnr:layers-apply "S-FTG,S-TEXT")
  (setq l (rnr:getposreal "Footing length (mm)" 1800.0) w (rnr:getposreal "Footing width (mm)" 1800.0)
        thk (rnr:getposreal "Thickness (mm)" 450.0) id (rnr:getstr "Footing ID" "F1"))
  (while (setq p (getpoint "\nFooting centre <done>: "))
    (rnr:rect p l w "S-FTG")
    (setq c (* 0.2 (min l w)))
    (rnr:rect p (* 2 c) (* 2 c) "S-FTG")
    (rnr:text (list (car p) (- (cadr p) (/ w 2.0) 250)) (strcat id " " (rtos l 2 0) "x" (rtos w 2 0) "x" (rtos thk 2 0)) (* 2.5 (rnr:scale)) "S-TEXT"))
  (rnr:end) (rnr:ok))
(princ)
