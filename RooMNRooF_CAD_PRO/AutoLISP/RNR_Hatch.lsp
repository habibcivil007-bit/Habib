;;; RNR_Hatch.lsp - material hatch shortcuts (predefined patterns; custom RNR_* need Hatch folder on support path)
(setq *RNR-MATS*
  '(("CONCRETE" "AR-CONC" 1.0 0) ("RCC" "RNR_RCC" 10.0 0) ("BRICK" "RNR_BRICK" 10.0 0) ("BLOCK" "AR-B816" 1.0 0)
    ("STONE" "RNR_STONE" 10.0 0) ("MARBLE" "RNR_MARBLE" 10.0 0) ("TILE" "RNR_TILE" 1.0 0) ("WOOD" "RNR_WOOD" 10.0 0)
    ("SAND" "AR-SAND" 1.0 0) ("EARTH" "EARTH" 20.0 45) ("SOIL" "RNR_SOIL" 10.0 0) ("WATER" "RNR_WATER" 10.0 0)
    ("GRASS" "GRASS" 10.0 0) ("GLASS" "RNR_GLASS" 10.0 45) ("STEEL" "STEEL" 10.0 0) ("INSULATION" "RNR_INSUL" 10.0 0)))

(defun c:RNRL-HATCH ( / m rec p pat)
  (rnr:start '("CMDECHO" "HPNAME" "HPSCALE" "HPANG" "CLAYER"))
  (setvar "CMDECHO" 0)
  (rnr:layers-apply "A-HATCH")
  (setq m (strcase (rnr:getstr "Material (CONCRETE/RCC/BRICK/STONE/TILE/WOOD/SAND/EARTH/...)" "CONCRETE")))
  (if (setq rec (assoc m *RNR-MATS*))
    (progn
      (setq pat (nth 1 rec))
      (if (and (wcmatch pat "RNR_*") (not (findfile (strcat pat ".pat"))))
        (progn (princ (strcat "\n[RNR] " pat ".pat not on support path - ANSI31 used.")) (setq pat "ANSI31")))
      (setvar "CLAYER" "A-HATCH")
      (while (setq p (getpoint "\nPick internal point <done>: "))
        (command "_.-HATCH" "_P" pat (nth 2 rec) (nth 3 rec) p ""))
      (rnr:ok))
    (princ "\n[RNR] Invalid input. Unknown material."))
  (rnr:end) (princ))
(princ)
