;;; RNR_BlockDefs.lsp - GENERATED by Scripts/generate_block_library.py - do not edit.
;;; Lets the LISP Edition create the 29 RooMNRooF block definitions with entmake (no .NET needed).
;;; Geometry on layer 0 (inherits insert layer). Existing definitions are never redefined.

(defun rnr:bd-line (a b) (entmake (list '(0 . "LINE") '(8 . "0") (cons 10 a) (cons 11 b))))
(defun rnr:bd-circle (c r) (entmake (list '(0 . "CIRCLE") '(8 . "0") (cons 10 c) (cons 40 r))))
(defun rnr:bd-arc (c r a0 a1) (entmake (list '(0 . "ARC") '(8 . "0") (cons 10 c) (cons 40 r) (cons 50 (* pi (/ a0 180.0))) (cons 51 (* pi (/ a1 180.0))))))
(defun rnr:bd-pline (closed pts)
  (entmake (append (list '(0 . "LWPOLYLINE") '(100 . "AcDbEntity") '(8 . "0") '(100 . "AcDbPolyline")
                         (cons 90 (length pts)) (cons 70 (if closed 1 0)))
                   (mapcar '(lambda (p) (cons 10 (list (car p) (cadr p)))) pts))))
(defun rnr:bd-text (p h s) (entmake (list '(0 . "TEXT") '(8 . "0") (cons 10 p) (cons 11 p) (cons 40 h)
 (cons 1 s) '(72 . 1) '(73 . 2))))
(defun rnr:bd-att (p h tag prm def) (entmake (list '(0 . "ATTDEF") '(8 . "0") (cons 10 p) (cons 11 p)
 (cons 40 h) (cons 1 def) (cons 3 prm) (cons 2 tag) '(70 . 0) '(72 . 1) '(74 . 2))))

(setq *RNR-BLOCK-LAYERS* '(
  ("RNR_DOOR" . "A-DOOR")
  ("RNR_WINDOW" . "A-WINDOW")
  ("RNR_BED_DOUBLE" . "A-FURN")
  ("RNR_SOFA" . "A-FURN")
  ("RNR_DINING" . "A-FURN")
  ("RNR_CHAIR" . "A-FURN")
  ("RNR_KITCHEN_COUNTER" . "A-FIXTURE")
  ("RNR_SINK" . "A-FIXTURE")
  ("RNR_TOILET" . "A-FIXTURE")
  ("RNR_BASIN" . "A-FIXTURE")
  ("RNR_SHOWER" . "A-FIXTURE")
  ("RNR_BATHTUB" . "A-FIXTURE")
  ("RNR_WARDROBE" . "A-FURN")
  ("RNR_TV" . "A-FURN")
  ("RNR_DESK" . "A-FURN")
  ("RNR_CAR" . "C-SITE")
  ("RNR_TREE" . "C-TREE")
  ("RNR_PLANT" . "C-TREE")
  ("RNR_LIGHT" . "E-LIGHT")
  ("RNR_FAN" . "E-POWER")
  ("RNR_AC" . "M-EQUIP")
  ("RNR_LIFT" . "A-STAIR")
  ("RNR_STAIR_ARROW" . "A-STAIR")
  ("RNR_NORTH" . "ANNO-NORTH")
  ("RNR_GRIDBUBBLE" . "ANNO-GRID")
  ("RNR_LEVEL" . "ANNO-LEVEL")
  ("RNR_SECTIONMARK" . "ANNO-SECTION")
  ("RNR_DETAILMARK" . "ANNO-DETAIL")
  ("RNR_ELEVMARK" . "ANNO-SECTION")
))

(defun rnr:block-names () (mapcar 'car *RNR-BLOCK-LAYERS*))

(defun rnr:block-layer (name / a) (if (setq a (assoc (strcase name) *RNR-BLOCK-LAYERS*)) (cdr a) "0"))

(defun rnr:define-block (name / n)
  ;; returns T when the block exists afterwards
  (setq n (strcase name))
  (cond
    ((tblsearch "BLOCK" n) T)
    ((not (assoc n *RNR-BLOCK-LAYERS*)) nil)
    (T
     (cond
      ((= n "RNR_DOOR")
       (entmake (list '(0 . "BLOCK") '(2 . "RNR_DOOR") '(70 . 0) '(10 0.0 0.0 0.0)))
       (rnr:bd-pline T (list (list 0 0) (list 40 0) (list 40 900) (list 0 900)))
       (rnr:bd-arc (list 0 0 0.0) 900 0 90)
       (rnr:bd-line (list 0 0 0.0) (list 900 0 0.0))
       (entmake '((0 . "ENDBLK"))))
      ((= n "RNR_WINDOW")
       (entmake (list '(0 . "BLOCK") '(2 . "RNR_WINDOW") '(70 . 0) '(10 0.0 0.0 0.0)))
       (rnr:bd-pline T (list (list 0 -125) (list 1200 -125) (list 1200 125) (list 0 125)))
       (rnr:bd-line (list 0 -42 0.0) (list 1200 -42 0.0))
       (rnr:bd-line (list 0 42 0.0) (list 1200 42 0.0))
       (entmake '((0 . "ENDBLK"))))
      ((= n "RNR_BED_DOUBLE")
       (entmake (list '(0 . "BLOCK") '(2 . "RNR_BED_DOUBLE") '(70 . 0) '(10 0.0 0.0 0.0)))
       (rnr:bd-pline T (list (list 0 0) (list 1500 0) (list 1500 2000) (list 0 2000)))
       (rnr:bd-pline T (list (list 0 1800) (list 1500 1800) (list 1500 2000) (list 0 2000)))
       (rnr:bd-pline T (list (list 100 1450) (list 650 1450) (list 650 1750) (list 100 1750)))
       (rnr:bd-pline T (list (list 850 1450) (list 1400 1450) (list 1400 1750) (list 850 1750)))
       (rnr:bd-line (list 0 1300 0.0) (list 1500 1300 0.0))
       (entmake '((0 . "ENDBLK"))))
      ((= n "RNR_SOFA")
       (entmake (list '(0 . "BLOCK") '(2 . "RNR_SOFA") '(70 . 0) '(10 0.0 0.0 0.0)))
       (rnr:bd-pline T (list (list 0 0) (list 2100 0) (list 2100 850) (list 0 850)))
       (rnr:bd-pline T (list (list 0 650) (list 2100 650) (list 2100 850) (list 0 850)))
       (rnr:bd-pline T (list (list 0 0) (list 200 0) (list 200 650) (list 0 650)))
       (rnr:bd-pline T (list (list 1900 0) (list 2100 0) (list 2100 650) (list 1900 650)))
       (rnr:bd-line (list 700 0 0.0) (list 700 650 0.0))
       (rnr:bd-line (list 1400 0 0.0) (list 1400 650 0.0))
       (entmake '((0 . "ENDBLK"))))
      ((= n "RNR_DINING")
       (entmake (list '(0 . "BLOCK") '(2 . "RNR_DINING") '(70 . 0) '(10 0.0 0.0 0.0)))
       (rnr:bd-pline T (list (list 0 0) (list 1600 0) (list 1600 900) (list 0 900)))
       (rnr:bd-pline T (list (list 175 -525) (list 625 -525) (list 625 -75) (list 175 -75)))
       (rnr:bd-pline T (list (list 175 975) (list 625 975) (list 625 1425) (list 175 1425)))
       (rnr:bd-pline T (list (list 975 -525) (list 1425 -525) (list 1425 -75) (list 975 -75)))
       (rnr:bd-pline T (list (list 975 975) (list 1425 975) (list 1425 1425) (list 975 1425)))
       (entmake '((0 . "ENDBLK"))))
      ((= n "RNR_CHAIR")
       (entmake (list '(0 . "BLOCK") '(2 . "RNR_CHAIR") '(70 . 0) '(10 0.0 0.0 0.0)))
       (rnr:bd-pline T (list (list 0 0) (list 450 0) (list 450 450) (list 0 450)))
       (rnr:bd-pline T (list (list 0 400) (list 450 400) (list 450 480) (list 0 480)))
       (entmake '((0 . "ENDBLK"))))
      ((= n "RNR_KITCHEN_COUNTER")
       (entmake (list '(0 . "BLOCK") '(2 . "RNR_KITCHEN_COUNTER") '(70 . 0) '(10 0.0 0.0 0.0)))
       (rnr:bd-pline T (list (list 0 0) (list 2400 0) (list 2400 600) (list 0 600)))
       (rnr:bd-line (list 0 560 0.0) (list 2400 560 0.0))
       (rnr:bd-pline T (list (list 450 100) (list 950 100) (list 950 500) (list 450 500)))
       (rnr:bd-circle (list 1700 200 0.0) 90)
       (rnr:bd-circle (list 1700 420 0.0) 90)
       (rnr:bd-circle (list 1950 200 0.0) 90)
       (rnr:bd-circle (list 1950 420 0.0) 90)
       (entmake '((0 . "ENDBLK"))))
      ((= n "RNR_SINK")
       (entmake (list '(0 . "BLOCK") '(2 . "RNR_SINK") '(70 . 0) '(10 0.0 0.0 0.0)))
       (rnr:bd-pline T (list (list 0 0) (list 800 0) (list 800 500) (list 0 500)))
       (rnr:bd-pline T (list (list 60 60) (list 740 60) (list 740 440) (list 60 440)))
       (rnr:bd-circle (list 400 380 0.0) 25)
       (entmake '((0 . "ENDBLK"))))
      ((= n "RNR_TOILET")
       (entmake (list '(0 . "BLOCK") '(2 . "RNR_TOILET") '(70 . 0) '(10 0.0 0.0 0.0)))
       (rnr:bd-pline T (list (list -250 0) (list 250 0) (list 250 180) (list -250 180)))
       (rnr:bd-pline T (list (list -180 180) (list 180 180) (list 180 300) (list -180 300)))
       (rnr:bd-arc (list 0 450 0.0) 180 180 360)
       (rnr:bd-line (list -180 450 0.0) (list -180 300 0.0))
       (rnr:bd-line (list 180 450 0.0) (list 180 300 0.0))
       (rnr:bd-arc (list 0 450 0.0) 180 0 180)
       (entmake '((0 . "ENDBLK"))))
      ((= n "RNR_BASIN")
       (entmake (list '(0 . "BLOCK") '(2 . "RNR_BASIN") '(70 . 0) '(10 0.0 0.0 0.0)))
       (rnr:bd-pline T (list (list -275 0) (list 275 0) (list 275 420) (list -275 420)))
       (rnr:bd-circle (list 0 210 0.0) 160)
       (rnr:bd-circle (list 0 330 0.0) 20)
       (entmake '((0 . "ENDBLK"))))
      ((= n "RNR_SHOWER")
       (entmake (list '(0 . "BLOCK") '(2 . "RNR_SHOWER") '(70 . 0) '(10 0.0 0.0 0.0)))
       (rnr:bd-pline T (list (list 0 0) (list 900 0) (list 900 900) (list 0 900)))
       (rnr:bd-line (list 0 0 0.0) (list 900 900 0.0))
       (rnr:bd-line (list 0 900 0.0) (list 900 0 0.0))
       (rnr:bd-circle (list 450 450 0.0) 50)
       (entmake '((0 . "ENDBLK"))))
      ((= n "RNR_BATHTUB")
       (entmake (list '(0 . "BLOCK") '(2 . "RNR_BATHTUB") '(70 . 0) '(10 0.0 0.0 0.0)))
       (rnr:bd-pline T (list (list 0 0) (list 1700 0) (list 1700 750) (list 0 750)))
       (rnr:bd-pline T (list (list 80 80) (list 1620 80) (list 1620 670) (list 80 670)))
       (rnr:bd-circle (list 1500 375 0.0) 40)
       (entmake '((0 . "ENDBLK"))))
      ((= n "RNR_WARDROBE")
       (entmake (list '(0 . "BLOCK") '(2 . "RNR_WARDROBE") '(70 . 0) '(10 0.0 0.0 0.0)))
       (rnr:bd-pline T (list (list 0 0) (list 1800 0) (list 1800 600) (list 0 600)))
       (rnr:bd-line (list 900 0 0.0) (list 900 600 0.0))
       (rnr:bd-line (list 0 520 0.0) (list 1800 520 0.0))
       (rnr:bd-line (list 60 300 0.0) (list 1740 300 0.0))
       (entmake '((0 . "ENDBLK"))))
      ((= n "RNR_TV")
       (entmake (list '(0 . "BLOCK") '(2 . "RNR_TV") '(70 . 0) '(10 0.0 0.0 0.0)))
       (rnr:bd-pline T (list (list 0 0) (list 1800 0) (list 1800 450) (list 0 450)))
       (rnr:bd-pline T (list (list 300 350) (list 1500 350) (list 1500 410) (list 300 410)))
       (entmake '((0 . "ENDBLK"))))
      ((= n "RNR_DESK")
       (entmake (list '(0 . "BLOCK") '(2 . "RNR_DESK") '(70 . 0) '(10 0.0 0.0 0.0)))
       (rnr:bd-pline T (list (list 0 0) (list 1200 0) (list 1200 600) (list 0 600)))
       (rnr:bd-pline T (list (list 375 -475) (list 825 -475) (list 825 -25) (list 375 -25)))
       (entmake '((0 . "ENDBLK"))))
      ((= n "RNR_CAR")
       (entmake (list '(0 . "BLOCK") '(2 . "RNR_CAR") '(70 . 0) '(10 0.0 0.0 0.0)))
       (rnr:bd-pline T (list (list 0 300) (list 300 0) (list 1500 0) (list 1800 300) (list 1800 4500) (list 1500 4800) (list 300 4800) (list 0 4500)))
       (rnr:bd-pline T (list (list 200 1300) (list 1600 1300) (list 1600 2100) (list 200 2100)))
       (rnr:bd-pline T (list (list 200 3300) (list 1600 3300) (list 1600 3900) (list 200 3900)))
       (rnr:bd-text (list 900 2700 0.0) 250 "CAR")
       (entmake '((0 . "ENDBLK"))))
      ((= n "RNR_TREE")
       (entmake (list '(0 . "BLOCK") '(2 . "RNR_TREE") '(70 . 0) '(10 0.0 0.0 0.0)))
       (rnr:bd-circle (list 0 0 0.0) 1500)
       (rnr:bd-circle (list 0 0 0.0) 100)
       (rnr:bd-line (list 100 0 0.0) (list 1300 0 0.0))
       (rnr:bd-line (list 70.7107 70.7107 0.0) (list 919.2388 919.2388 0.0))
       (rnr:bd-line (list 0 100 0.0) (list 0 1300 0.0))
       (rnr:bd-line (list -70.7107 70.7107 0.0) (list -919.2388 919.2388 0.0))
       (rnr:bd-line (list -100 0 0.0) (list -1300 0 0.0))
       (rnr:bd-line (list -70.7107 -70.7107 0.0) (list -919.2388 -919.2388 0.0))
       (rnr:bd-line (list -0 -100 0.0) (list -0 -1300 0.0))
       (rnr:bd-line (list 70.7107 -70.7107 0.0) (list 919.2388 -919.2388 0.0))
       (entmake '((0 . "ENDBLK"))))
      ((= n "RNR_PLANT")
       (entmake (list '(0 . "BLOCK") '(2 . "RNR_PLANT") '(70 . 0) '(10 0.0 0.0 0.0)))
       (rnr:bd-circle (list 0 0 0.0) 300)
       (rnr:bd-circle (list 0 0 0.0) 150)
       (rnr:bd-line (list -300 0 0.0) (list 300 0 0.0))
       (rnr:bd-line (list 0 -300 0.0) (list 0 300 0.0))
       (entmake '((0 . "ENDBLK"))))
      ((= n "RNR_LIGHT")
       (entmake (list '(0 . "BLOCK") '(2 . "RNR_LIGHT") '(70 . 0) '(10 0.0 0.0 0.0)))
       (rnr:bd-circle (list 0 0 0.0) 150)
       (rnr:bd-line (list -106 -106 0.0) (list 106 106 0.0))
       (rnr:bd-line (list -106 106 0.0) (list 106 -106 0.0))
       (entmake '((0 . "ENDBLK"))))
      ((= n "RNR_FAN")
       (entmake (list '(0 . "BLOCK") '(2 . "RNR_FAN") '(70 . 0) '(10 0.0 0.0 0.0)))
       (rnr:bd-circle (list 0 0 0.0) 100)
       (rnr:bd-pline T (list (list -60 100) (list -80 600) (list 80 600) (list 60 100)))
       (rnr:bd-pline T (list (list -56.6025 -101.9615) (list -479.6152 -369.282) (list -559.6152 -230.718) (list -116.6025 1.9615)))
       (rnr:bd-pline T (list (list 116.6025 1.9615) (list 559.6152 -230.718) (list 479.6152 -369.282) (list 56.6025 -101.9615)))
       (entmake '((0 . "ENDBLK"))))
      ((= n "RNR_AC")
       (entmake (list '(0 . "BLOCK") '(2 . "RNR_AC") '(70 . 0) '(10 0.0 0.0 0.0)))
       (rnr:bd-pline T (list (list 0 0) (list 1000 0) (list 1000 250) (list 0 250)))
       (rnr:bd-line (list 50 60 0.0) (list 950 60 0.0))
       (rnr:bd-line (list 50 120 0.0) (list 950 120 0.0))
       (rnr:bd-text (list 500 180 0.0) 60 "AC")
       (entmake '((0 . "ENDBLK"))))
      ((= n "RNR_LIFT")
       (entmake (list '(0 . "BLOCK") '(2 . "RNR_LIFT") '(70 . 0) '(10 0.0 0.0 0.0)))
       (rnr:bd-pline T (list (list 0 0) (list 1800 0) (list 1800 1800) (list 0 1800)))
       (rnr:bd-pline T (list (list 150 150) (list 1650 150) (list 1650 1500) (list 150 1500)))
       (rnr:bd-line (list 150 150 0.0) (list 1650 1500 0.0))
       (rnr:bd-line (list 150 1500 0.0) (list 1650 150 0.0))
       (rnr:bd-line (list 450 1650 0.0) (list 1350 1650 0.0))
       (entmake '((0 . "ENDBLK"))))
      ((= n "RNR_STAIR_ARROW")
       (entmake (list '(0 . "BLOCK") '(2 . "RNR_STAIR_ARROW") '(70 . 0) '(10 0.0 0.0 0.0)))
       (rnr:bd-line (list 0 0 0.0) (list 0 2000 0.0))
       (rnr:bd-pline nil (list (list -120 1780) (list 0 2000) (list 120 1780)))
       (rnr:bd-circle (list 0 0 0.0) 50)
       (rnr:bd-text (list 0 -250 0.0) 150 "UP")
       (entmake '((0 . "ENDBLK"))))
      ((= n "RNR_NORTH")
       (entmake (list '(0 . "BLOCK") '(2 . "RNR_NORTH") '(70 . 0) '(10 0.0 0.0 0.0)))
       (rnr:bd-circle (list 0 0 0.0) 800)
       (rnr:bd-pline T (list (list 0 800) (list -320 -480) (list 0 -160) (list 320 -480)))
       (rnr:bd-text (list 0 1100 0.0) 300 "N")
       (entmake '((0 . "ENDBLK"))))
      ((= n "RNR_GRIDBUBBLE")
       (entmake (list '(0 . "BLOCK") '(2 . "RNR_GRIDBUBBLE") '(70 . 2) '(10 0.0 0.0 0.0)))
       (rnr:bd-circle (list 0 0 0.0) 500)
       (rnr:bd-att (list 0 0 0.0) 350 "GRID" "Grid label" "A")
       (entmake '((0 . "ENDBLK"))))
      ((= n "RNR_LEVEL")
       (entmake (list '(0 . "BLOCK") '(2 . "RNR_LEVEL") '(70 . 2) '(10 0.0 0.0 0.0)))
       (rnr:bd-pline T (list (list 0 0) (list -150 250) (list 150 250)))
       (rnr:bd-line (list 0 0 0.0) (list 1800 0 0.0))
       (rnr:bd-att (list 900 150 0.0) 200 "LEVEL" "Level" "+0.000")
       (rnr:bd-att (list 900 450 0.0) 150 "NAME" "Level name" "FFL")
       (entmake '((0 . "ENDBLK"))))
      ((= n "RNR_SECTIONMARK")
       (entmake (list '(0 . "BLOCK") '(2 . "RNR_SECTIONMARK") '(70 . 2) '(10 0.0 0.0 0.0)))
       (rnr:bd-circle (list 0 0 0.0) 600)
       (rnr:bd-line (list -600 0 0.0) (list 600 0 0.0))
       (rnr:bd-pline T (list (list 600 0) (list 600 700) (list 1100 0)))
       (rnr:bd-att (list 0 280 0.0) 280 "NO" "Section no" "A")
       (rnr:bd-att (list 0 -300 0.0) 200 "SHEET" "Sheet" "A-201")
       (entmake '((0 . "ENDBLK"))))
      ((= n "RNR_DETAILMARK")
       (entmake (list '(0 . "BLOCK") '(2 . "RNR_DETAILMARK") '(70 . 2) '(10 0.0 0.0 0.0)))
       (rnr:bd-circle (list 0 0 0.0) 600)
       (rnr:bd-line (list -600 0 0.0) (list 600 0 0.0))
       (rnr:bd-att (list 0 280 0.0) 280 "NO" "Detail no" "1")
       (rnr:bd-att (list 0 -300 0.0) 200 "SHEET" "Sheet" "S-301")
       (entmake '((0 . "ENDBLK"))))
      ((= n "RNR_ELEVMARK")
       (entmake (list '(0 . "BLOCK") '(2 . "RNR_ELEVMARK") '(70 . 2) '(10 0.0 0.0 0.0)))
       (rnr:bd-circle (list 0 0 0.0) 600)
       (rnr:bd-pline T (list (list -600 0) (list 0 850) (list 600 0)))
       (rnr:bd-att (list 0 0 0.0) 300 "NO" "Elevation no" "1")
       (entmake '((0 . "ENDBLK"))))
     )
     (if (tblsearch "BLOCK" n) T nil))))

(defun c:RNRL-BLOCKS ( / c)
  ;; define all 29 blocks in the current drawing (skips existing ones)
  (setq c 0)
  (foreach n (rnr:block-names) (if (rnr:define-block n) (setq c (1+ c))))
  (princ (strcat "\n[RNR] " (itoa c) " of " (itoa (length *RNR-BLOCK-LAYERS*)) " RNR blocks available."))
  (princ))
(princ)
