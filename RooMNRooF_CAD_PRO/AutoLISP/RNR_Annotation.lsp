;;; RNR_Annotation.lsp - text styles, level marks, tags, north arrow (LISP)
(defun rnr:ensure-style (name font wf)
  (if (not (tblsearch "STYLE" name))
    (entmake (list '(0 . "STYLE") '(100 . "AcDbSymbolTableRecord") '(100 . "AcDbTextStyleTableRecord")
                   (cons 2 name) '(70 . 0) '(40 . 0.0) (cons 41 wf) '(50 . 0.0) '(71 . 0) '(42 . 2.5)
                   (cons 3 font) '(4 . ""))))
  name)

(defun c:RNRL-STYLES ()
  (rnr:ensure-style "RNR_TITLE" "arial.ttf" 1.0)
  (rnr:ensure-style "RNR_HEADING" "arial.ttf" 1.0)
  (rnr:ensure-style "RNR_TEXT" "arial.ttf" 0.9)
  (rnr:ensure-style "RNR_NOTE" "arialn.ttf" 1.0)
  (rnr:ensure-style "RNR_ROMANS" "romans.shx" 0.8)
  (princ "\n[RNR] RooMNRooF text styles ensured (non-annotative LISP version; use RNRSTYLES for annotative).")
  (princ))

(defun c:RNRL-LEVEL ( / p s sc)
  (rnr:start nil)
  (rnr:layers-apply "ANNO-LEVEL")
  (setq s (rnr:getstr "Level text" "+0.000 FFL") sc (rnr:scale))
  (while (setq p (getpoint "\nLevel point <done>: "))
    (rnr:lwpoly (list p (polar p (* 0.75 pi) (* 4.2 sc)) (polar p (* 0.25 pi) (* 4.2 sc))) T "ANNO-LEVEL")
    (rnr:line (polar p pi (* 6 sc)) (polar p 0 (* 14 sc)) "ANNO-LEVEL")
    (entmakex (list '(0 . "TEXT") '(8 . "ANNO-LEVEL") (cons 10 (polar (polar p 0 (* 4 sc)) (/ pi 2) (* 1 sc))) (cons 40 (* 2.5 sc)) (cons 1 s))))
  (rnr:end) (princ))

(defun c:RNRL-TAG ( / p s sc)
  (rnr:start nil)
  (rnr:layers-apply "ANNO-TAGS")
  (setq s (rnr:getstr "Tag" "C1") sc (rnr:scale))
  (while (setq p (getpoint "\nTag point <done>: "))
    (rnr:rect p (* 16 sc) (* 8 sc) "ANNO-TAGS")
    (rnr:text p s (* 3 sc) "ANNO-TAGS"))
  (rnr:end) (princ))

(defun c:RNRL-NORTH ( / p sc)
  (rnr:start nil)
  (rnr:layers-apply "ANNO-NORTH")
  (setq sc (rnr:scale))
  (if (setq p (getpoint "\nNorth arrow centre: "))
    (progn
      (rnr:circle p (* 10 sc) "ANNO-NORTH")
      (rnr:lwpoly (list (polar p (* 1.5 pi) (* 9 sc)) (polar p (/ pi 2) (* 12 sc)) (polar p pi (* 4 sc))) T "ANNO-NORTH")
      (rnr:lwpoly (list (polar p (* 1.5 pi) (* 9 sc)) (polar p (/ pi 2) (* 12 sc)) (polar p 0 (* 4 sc))) T "ANNO-NORTH")
      (rnr:text (polar p (/ pi 2) (* 15 sc)) "N" (* 3.5 sc) "ANNO-NORTH")))
  (rnr:end) (princ))
(princ)
