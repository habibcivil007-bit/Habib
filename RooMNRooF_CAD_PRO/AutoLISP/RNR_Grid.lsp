;;; RNR_Grid.lsp - structural grid generator (LISP version of RNRGRID)
(defun rnr:grid-letter (i / s letters)
  (setq letters "ABCDEFGHJKLMNPQRSTUVWXYZ" s "" i (1+ i))
  (while (> i 0)
    (setq s (strcat (substr letters (1+ (rem (1- i) 24)) 1) s) i (/ (1- i) 24)))
  s)

(defun rnr:parse-spacings (str / out parts n v)
  ;; "3*5000" or "4500,5000,4500"
  (foreach tok (rnr:split str ",")
    (if (setq parts (vl-string-search "*" tok))
      (progn (setq n (atoi (substr tok 1 parts)) v (atof (substr tok (+ parts 2))))
             (repeat n (setq out (cons v out))))
      (setq out (cons (atof tok) out))))
  (vl-remove-if '(lambda (x) (<= x 0)) (reverse out)))

(defun c:RNRL-GRID ( / xs ys ext o sc r xacc yacc xmax ymax x y i lbl)
  (rnr:start '("CMDECHO" "OSMODE"))
  (setvar "CMDECHO" 0)
  (setq xs (rnr:parse-spacings (rnr:getstr "X spacings" "3*5000"))
        ys (rnr:parse-spacings (rnr:getstr "Y spacings" "2*4500"))
        ext (rnr:getposreal "Extension" 1500.0)
        o (getpoint "\nGrid origin: ")
        sc (rnr:scale) r (* 5.0 sc))
  (if (and o xs ys)
    (progn
      (setvar "OSMODE" 0)
      (rnr:layers-apply "S-GRID,ANNO-GRID")
      (setq xacc '(0.0) yacc '(0.0))
      (foreach d xs (setq xacc (cons (+ (car xacc) d) xacc)))
      (foreach d ys (setq yacc (cons (+ (car yacc) d) yacc)))
      (setq xacc (reverse xacc) yacc (reverse yacc) xmax (last xacc) ymax (last yacc) i 0)
      (foreach x xacc
        (setq lbl (itoa (1+ i)))
        (rnr:line (list (+ (car o) x) (- (cadr o) ext)) (list (+ (car o) x) (+ (cadr o) ymax ext)) "S-GRID")
        (rnr:circle (list (+ (car o) x) (- (cadr o) ext r)) r "ANNO-GRID")
        (rnr:text (list (+ (car o) x) (- (cadr o) ext r)) lbl (* 4.0 sc) "ANNO-GRID")
        (setq i (1+ i)))
      (setq i 0)
      (foreach y yacc
        (setq lbl (rnr:grid-letter i))
        (rnr:line (list (- (car o) ext) (+ (cadr o) y)) (list (+ (car o) xmax ext) (+ (cadr o) y)) "S-GRID")
        (rnr:circle (list (- (car o) ext r) (+ (cadr o) y)) r "ANNO-GRID")
        (rnr:text (list (- (car o) ext r) (+ (cadr o) y)) lbl (* 4.0 sc) "ANNO-GRID")
        (setq i (1+ i)))
      (princ (strcat "\n[RNR] Grid " (itoa (length xacc)) " x " (itoa (length yacc)) " created.")))
    (princ "\n[RNR] Invalid input."))
  (rnr:end) (princ))
(princ)
