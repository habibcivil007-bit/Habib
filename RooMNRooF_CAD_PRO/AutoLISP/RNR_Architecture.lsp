;;; RNR_Architecture.lsp - walls, doors, windows, room generator (LISP versions)
(defun rnr:wall-band (a b thk lay / ang p1 p2 p3 p4)
  (setq ang (+ (angle a b) (/ pi 2)))
  (setq p1 (polar a ang (/ thk 2.0)) p2 (polar b ang (/ thk 2.0))
        p3 (polar b (+ ang pi) (/ thk 2.0)) p4 (polar a (+ ang pi) (/ thk 2.0)))
  (rnr:lwpoly (list p1 p2 p3 p4) T lay))

(defun c:RNRL-WALL ( / thk a b)
  (rnr:start '("CMDECHO" "OSMODE"))
  (rnr:layers-apply "A-WALL")
  (setq thk (rnr:getposreal "Wall thickness (mm)" 250.0))
  (if (setq a (getpoint "\nWall start point: "))
    (while (setq b (getpoint a "\nNext point <done>: "))
      (rnr:wall-band a b thk "A-WALL")
      (setq a b)))
  (rnr:end) (rnr:ok))

(defun rnr:door (p w ang / e)
  ;; leaf + 90 deg swing arc
  (rnr:line p (polar p (+ ang (/ pi 2)) w) "A-DOOR")
  (entmakex (list '(0 . "ARC") '(8 . "A-DOOR") (cons 10 p) (cons 40 w) (cons 50 ang) (cons 51 (+ ang (/ pi 2))))))

(defun c:RNRL-DOOR ( / p w a)
  (rnr:start nil)
  (rnr:layers-apply "A-DOOR")
  (setq w (rnr:getposreal "Door width (mm)" 900.0))
  (if (setq p (getpoint "\nHinge point: "))
    (progn (setq a (getangle p "\nWall direction <0>: ")) (rnr:door p w (if a a 0.0))))
  (rnr:end) (rnr:ok))

(defun rnr:window (p w thk ang / n)
  (setq n (+ ang (/ pi 2)))
  (rnr:lwpoly (list (polar p n (/ thk 2.0)) (polar (polar p ang w) n (/ thk 2.0))
                    (polar (polar p ang w) (+ n pi) (/ thk 2.0)) (polar p (+ n pi) (/ thk 2.0))) T "A-WINDOW")
  (rnr:line (polar p n 25.0) (polar (polar p ang w) n 25.0) "A-GLAZ")
  (rnr:line (polar p (+ n pi) 25.0) (polar (polar p ang w) (+ n pi) 25.0) "A-GLAZ"))

(defun c:RNRL-WINDOW ( / p w thk a)
  (rnr:start nil)
  (rnr:layers-apply "A-WINDOW,A-GLAZ")
  (setq w (rnr:getposreal "Window width (mm)" 1200.0) thk (rnr:getposreal "Wall thickness (mm)" 250.0))
  (if (setq p (getpoint "\nWindow start (wall centre-line): "))
    (progn (setq a (getangle p "\nWall direction <0>: ")) (rnr:window p w thk (if a a 0.0))))
  (rnr:end) (rnr:ok))

(defun c:RNRL-ROOM ( / L W thk nm o x y sc area)
  (rnr:start '("CMDECHO" "OSMODE"))
  (setvar "OSMODE" 0)
  (rnr:layers-apply "A-WALL,A-ROOM,A-DOOR,A-WINDOW,A-GLAZ")
  (setq L (rnr:getposreal "Internal length (mm)" 4000.0) W (rnr:getposreal "Internal width (mm)" 3500.0)
        thk (rnr:getposreal "Wall thickness (mm)" 250.0) nm (rnr:getstr "Room name" "BED ROOM"))
  (if (setq o (getpoint "\nInternal lower-left corner: "))
    (progn
      (setq x (car o) y (cadr o) sc (rnr:scale) area (/ (* L W) 1e6))
      (rnr:lwpoly (list o (list (+ x L) y) (list (+ x L) (+ y W)) (list x (+ y W))) T "A-WALL")
      (rnr:lwpoly (list (list (- x thk) (- y thk)) (list (+ x L thk) (- y thk)) (list (+ x L thk) (+ y W thk)) (list (- x thk) (+ y W thk))) T "A-WALL")
      (rnr:lwpoly (list o (list (+ x L) y) (list (+ x L) (+ y W)) (list x (+ y W))) T "A-ROOM")
      (rnr:door (list (- (+ x (/ L 2.0)) 450.0) (- y (/ thk 2.0))) 900.0 0.0)
      (rnr:window (list (- (+ x (/ L 2.0)) 750.0) (+ y W (/ thk 2.0))) 1500.0 thk 0.0)
      (rnr:text (list (+ x (/ L 2.0)) (+ y (/ W 2.0) (* 2.5 sc))) (strcase nm) (* 3.0 sc) "A-ROOM")
      (rnr:text (list (+ x (/ L 2.0)) (- (+ y (/ W 2.0)) (* 2.5 sc))) (strcat (rtos area 2 2) " m2") (* 2.2 sc) "A-ROOM")
      (princ (strcat "\n[RNR] Room " nm " = " (rtos area 2 2) " m2."))))
  (rnr:end) (princ))
(princ)
